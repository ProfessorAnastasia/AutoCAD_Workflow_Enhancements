; AutoSave Script for AutoCAD Mechanical 2026
; Saves incrementally named .dwg files every 5 minutes
; Output: C:\Users\Administrator\Desktop\Outputs\

(defun start-autosave ( / )
  (setq save-interval 300)
  (setq save-folder "C:/Users/Administrator/Desktop/Outputs/")
  (setq *last-save-time* (getvar "DATE"))
  (setq *save-count* 0)
  (setq *base-dwg-name* nil)
  (vlr-command-reactor nil '((:vlr-commandEnded . acm-check-and-save)))
  (princ "\n[AutoSave] Active — saving every 5 minutes to: ")
  (princ save-folder)
)

(defun acm-check-and-save (reactor params / current-time elapsed)
  (setq current-time (getvar "DATE"))
  (setq elapsed (* (- current-time *last-save-time*) 86400.0))
  (if (>= elapsed save-interval)
    (acm-do-save)
  )
)

(defun acm-minute-label (count interval / total-sec)
  (setq total-sec (* count interval))
  (if (= (rem total-sec 60) 0)
    (strcat (itoa (/ total-sec 60)) "m")
    (strcat (rtos (/ total-sec 60.0) 2 1) "m")
  )
)

(defun acm-strip-suffix (name / pos result)
  (setq result name)
  (setq pos (vl-string-search "_" name))
  (while pos
    (setq result (substr name 1 pos))
    (setq pos (vl-string-search "_" name (1+ pos)))
  )
  (if (= result "") name result)
)

(defun acm-do-save ( / raw-name save-path doc minute-label state-file f)
  (setq raw-name (vl-filename-base (getvar "DWGNAME")))
  (if (or (= raw-name "") (= raw-name "Drawing1"))
    (progn
      (princ "\n[AutoSave] Skipped — please save and name your drawing first.")
      (setq *last-save-time* (getvar "DATE"))
      (exit)
    )
  )
  (if (not *base-dwg-name*)
    (progn
      (setq *base-dwg-name* (acm-strip-suffix raw-name))
      (setq *save-count* 0)
      (setq state-file (strcat save-folder *base-dwg-name* "_autosave.state"))
      (if (findfile state-file)
        (progn
          (setq f (open state-file "r"))
          (setq *save-count* (atoi (read-line f)))
          (close f)
          (princ (strcat "\n[AutoSave] Session resumed — continuing from: "
                         (acm-minute-label *save-count* save-interval)))
        )
      )
    )
  )
  (setq *save-count* (1+ *save-count*))
  (setq minute-label (acm-minute-label *save-count* save-interval))
  (setq save-path (strcat save-folder *base-dwg-name* "_" minute-label ".dwg"))
  (setq doc (vla-get-activedocument (vlax-get-acad-object)))
  (vla-SaveAs doc save-path 64)
  (setq state-file (strcat save-folder *base-dwg-name* "_autosave.state"))
  (setq f (open state-file "w"))
  (write-line (itoa *save-count*) f)
  (close f)
  (setq *last-save-time* (getvar "DATE"))
  (princ (strcat "\n[AutoSave] Saved: " save-path))
)

(defun set-save-interval (new-interval)
  (setq save-interval new-interval)
  (princ (strcat "\n[AutoSave] Interval updated to: " (itoa new-interval) " seconds."))
  (princ)
)

(vl-load-com)
(start-autosave)
(princ)
